-- 3GPP TS 32.401 Performance Management statsfile schema
-- Encodes Ericsson PM statsfiles (C* core, G* HLR/vHLR variants)
-- Upload via: POST /api/schemas/upload?subdir=ericsson
-- Use in pipeline YAML:
--   serializer_in:
--     type: asn1
--     schema_file: /data/schemas/ericsson/3gpp_32401.asn
--     message_class: FileContent
--     encoding: ber

GPP-PM-32401 DEFINITIONS IMPLICIT TAGS ::= BEGIN

  FileContent ::= SEQUENCE {
    fileHeader  [0] FileHeader OPTIONAL,
    measData    [1] MeasData,
    endTime     [2] GeneralizedTime OPTIONAL
  }

  FileHeader ::= SEQUENCE {
    fileFormatVersion   [0] GraphicString OPTIONAL,
    senderName          [1] GraphicString OPTIONAL,
    senderType          [2] GraphicString OPTIONAL,
    vendorName          [3] GraphicString OPTIONAL,
    collectionBeginTime [4] GeneralizedTime OPTIONAL
  }

  MeasData     ::= SEQUENCE OF MeasCollection

  MeasCollection ::= SEQUENCE {
    managedElement [0] ManagedElement OPTIONAL,
    measInfoList   [1] SEQUENCE OF MeasInfo
  }

  ManagedElement ::= SEQUENCE {
    swVersion [0] GraphicString OPTIONAL,
    localDn   [1] GraphicString OPTIONAL
  }

  MeasInfo ::= SEQUENCE {
    measTimeStamp     [0] GeneralizedTime OPTIONAL,
    granularityPeriod [1] INTEGER OPTIONAL,
    measTypes         [2] SEQUENCE OF GraphicString,
    measValues        [3] SEQUENCE OF MeasValue
  }

  MeasValue ::= SEQUENCE {
    measObjLdn  [0] GraphicString,
    measResults [1] SEQUENCE OF MeasResult,
    suspect     [2] BOOLEAN OPTIONAL
  }

  MeasResult ::= CHOICE {
    iVal   [0] INTEGER,
    rVal   [1] REAL,
    isNull [2] NULL
  }

END
